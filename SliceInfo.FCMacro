# -*- coding: utf-8 -*-
import FreeCAD
import Mesh
import tempfile
import subprocess
from PySide import QtCore,QtGui

import __options__ as options
reload(options)

slicerOptions=[]
for iniFile in options.SLICER_INI_FILES:
	slicerOptions.append("--load")
	slicerOptions.append(iniFile)

doc=App.ActiveDocument
visibleObjs=[]
for obj in doc.Objects:
	if obj.ViewObject.isVisible():
		visibleObjs.append(obj)

stlFileName=tempfile.gettempdir()+"/temporary.stl"
gcodeFileName=tempfile.gettempdir()+"/temporary.gcode"

Mesh.export(visibleObjs,stlFileName)
slicerOutput=subprocess.check_output([options.SLICER]+
	slicerOptions+
	["--no-gui",stlFileName,"--output",gcodeFileName])

message=""
patterns=[
	"; generated by",
	"; total filament cost",
	"; estimated printing time",
	"; filament used"
]

for line in open(gcodeFileName):
	for pattern in patterns:
		if pattern in line:
			message+=line

dialog = QtGui.QMessageBox(QtGui.QMessageBox.Information,'Slice Info',message)
dialog.setWindowModality(QtCore.Qt.ApplicationModal)
dialog.exec_()
