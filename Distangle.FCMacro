import sys, os, FreeCAD, RaytracingGui, shutil, os.path, ImageGui, subprocess

if os.path.dirname(__file__) not in sys.path:
	sys.path.append(os.path.dirname(__file__))

import lib.DocumentDisentangler
reload (lib.DocumentDisentangler)
from lib.DocumentDisentangler import DocumentDisentangler

import lib.DialogUtil
reload(lib.DialogUtil)
from lib.DialogUtil import DialogUtil

def main():
	doc=FreeCAD.ActiveDocument

	if doc is None:
		DialogUtil.errorMessage("No current document.")
		return

	disentangler=DocumentDisentangler()
	disentangler.disentangle(doc)

main()
