# -*- coding: utf-8 -*-
import FreeCAD, Mesh, tempfile, subprocess
from PySide import QtCore, QtGui

import __options__ as options
reload(options)

def main():
	doc=App.ActiveDocument
	if doc is None:
		message="No document open"
		dialog=QtGui.QMessageBox(QtGui.QMessageBox.Information,'Error',message)
		dialog.setWindowModality(QtCore.Qt.ApplicationModal)
		dialog.exec_()
		return

	visibleObjs=[]

	for obj in doc.Objects:
		if obj.ViewObject.isVisible():
			visibleObjs.append(obj)

	f=tempfile.NamedTemporaryFile(suffix=".stl")
	fileName=f.name
	f.close()

	Mesh.export(visibleObjs,fileName)

	subprocess.Popen([options.SLICER,fileName])

main()
