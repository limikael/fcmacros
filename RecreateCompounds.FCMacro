# -*- coding: utf-8 -*-
from PySide import QtCore, QtGui

def main():
	doc=FreeCAD.ActiveDocument
	if doc is None:
		message="No document open"
		dialog=QtGui.QMessageBox(QtGui.QMessageBox.Warning,'Error',message)
		dialog.setWindowModality(QtCore.Qt.ApplicationModal)
		dialog.exec_()
		return

	for obj in doc.Objects:
		if obj.TypeId=="Part::Compound":
			label=obj.Label
			placement=obj.Placement
			visibility=obj.ViewObject.Visibility
			inList=obj.InList
			links=obj.Links
			name=obj.Name

			doc.removeObject(obj.Name)
			new=doc.addObject("Part::Compound",name)

			new.Links=links
			new.Label=label
			new.Placement=placement
			new.ViewObject.Visibility=visibility

			for parent in inList:
				parentLinks=parent.Links
				parentLinks.append(new)
				parent.Links=parentLinks

	doc.recompute()

main()
